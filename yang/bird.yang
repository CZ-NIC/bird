module bird {
  yang-version 1.1;
  namespace "https://bird.nic.cz/yang/v2.18/";
  prefix "bird";

  import ietf-yang-types {
    prefix "yang";
  }

  organization "cz.nic";
  contact "foo@b.ar";
  description "bird api based on 1:1 bird cli";

  revision "2026-02-10" {
    description "Specified show-memory RPC";
    reference "what";
  }

  grouping memory-info-line {
    description "Information about consumed memory of a specific kind";
    leaf effective {
      type uint64;
      units "byte";
      description "Memory we consider needed";
    }
    leaf overhead {
      type uint64;
      units "byte";
      description "Memory which is standby, unusable or technical";
    }
  }

  grouping cli-memory-info {
    description "Complete consumed memory info";
    container tables {
      description "Memory used by route objects in tables";
      uses memory-info-line;
    }
    container attributes {
      description "Memory used by attribute cache";
      uses memory-info-line;
    }
    container protocols {
      description "Memory used by the prorocols";
      uses memory-info-line;
    }
    container config {
      description "Current config";
      uses memory-info-line;
    }
    container total {
      description "All memory combined";
      uses memory-info-line;
    }

    container pages {
      description "Page allocator info";
      leaf active {
	type uint64;
	units "byte";
	description "Active pages";
      }
      leaf hot {
	type uint64;
	units "byte";
	description "Hot free pages";
      }
      leaf cold {
	type uint64;
	units "byte";
	description "Cold free pages";
      }
      leaf hot-rcu-failure-count {
	type uint64;
	description "Hot page cache depleted while in RCU";
      }
    }
  }

  rpc cli-show-memory {
    description "CLI: show memory";
    output {
      container show-memory-info {
	uses cli-memory-info;
	description "show memory output";
      }
    }
  }

  rpc cli-show-status {
    description "CLI: show status";
    output {
      leaf status {
	type string;
      }
    }
  }

  rpc cli-load-config {
    input {
      container load-config {
	leaf name {
	  type string;
	}
      }
    }
  }
}
