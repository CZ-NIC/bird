module show_status {

  namespace ".";
  
  prefix "show_status";

  description "cli show status format";

  typedef date-and-time {
    type string {
      pattern '\d{4}-\d{2}-\d{2}T\d{2}:\d{2}:\d{2}(\.\d+)?'
          + '(Z|[\+\-]\d{2}:\d{2})';
    }
  }

  grouping timer {
    leaf remains {
      type uint64;
    }
    leaf count_time {
      type uint64;
    }
  }


  container message {
    leaf version {
      type string;
    }
    container body {
      leaf router_id {
        type int32;
      }
      leaf hostname {
        type string;
      }
      leaf server_time {
        type int32;
      }
      leaf last_reboot {
        type int32;
      }
      leaf last_reconfiguration {
        type int32;
      }
      container gr_restart {
        leaf waiting_for_n_channels_to_recover {
          type int32;
        }
        container wait_timer {
          uses timer;
        }
      }
    }
    leaf state {
      type string;
    }
  }
}
